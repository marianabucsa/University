( defun insidew ( corner1 corner2 c )
  ( setq x1 ( car corner1 ) y1 ( cadr corner1 ) 
         x2 ( car corner2 ) y2 ( cadr corner2 ) 
         x ( car c ) y ( cadr c )
	 )
  ; verifica daca centrul se afla in interiorul  dreptunghiului
  ( and ( <= ( min x1 x2 ) x ) (<= x ( max x1 x2 ) )
        ( <= ( min y1 y2 ) y ) (<= y ( max y1 y2 ) )
       )
  )
( defun dist ( corner1 corner2 c )
  ; d1 d2 d3 d4 sunt distantele centrului fata de fiecare latura a dreptunghiului
  ( setq d1 ( abs ( - ( car corner2  ) ( car c ) ) ) )
  ( setq d2 ( abs ( - ( car corner1  ) ( car c ) ) ) )
  ( setq d3 ( abs ( - ( cadr corner2  ) ( cadr c ) ) ) )
  ( setq d4 ( abs ( - ( cadr corner1  ) ( cadr c ) ) ) )
  ; lista contine distanta minima dintre centru si lungimea/latimea dreptunghiului
  ( list ( min d1 d2 ) ( min d3 d4 ) )
 	 )
( defun projdist ( rad corner1 corner2 c )
   ( setq d ( dist corner1 corner2 c ) )
   ( and ( < rad ( car d ) ) ( < rad ( cadr d ) )  
	    )
  	)
;functia principala
( defun CIRCLEC ( )
  (initget 1)
  ( setq corner1 ( getpoint "\nselect corner point" ) )
  ( setq corner2 ( getcorner corner1 "\nselect corner point" ) )
  ( command "rectangle" corner1 corner2 )
  ( setq c ( getpoint "\nselect center point" ) )
  ( while ( not ( insidew corner1 corner2 c ) )
    ( setq c ( getpoint "\nselect center point" ) )
	)
  ( setq rad ( getdist c "\nenter circle radius" ) )
  ( while ( not ( projdist rad corner1 corner2 c) )
     (setq rad ( getdist c "\nenter circle radius" ) )
        )
  ( command "circle" c rad )
  ( command "erase" corner1 "" )
  	)
